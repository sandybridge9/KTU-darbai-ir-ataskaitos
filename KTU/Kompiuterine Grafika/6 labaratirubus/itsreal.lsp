(defun dtr (a)
    (* PI(/ a 180.0))); kampai laipsniais
; Illuminati braižymas
(DEFUN c:itsreal ()
 (SETQ Viršus (GETPOINT "\n Nurodykite trikampio viršunę"))
 (SETQ Ilgis (GETREAL "\n Įveskite kraštinės ilgį"))
 (SETQ pt1 (polar Viršus (dtr 240.0)Ilgis))
 (COMMAND "POLYGON" "3" "Edge" Viršus pt1)
 (SETQ Trikampis (entlast))
 (COMMAND "osnap" "OFF")
 (SETQ atstumas1 (sqrt(+(EXPT(-(car Viršus)(car pt1))2)(EXPT(-(cadr Viršus)(cadr pt1))2))))
 (SETQ pt2 (polar pt1 (dtr 0.0)Ilgis))
 (SETQ pt3 (polar pt1 (dtr 60.0)(/ atstumas1 3)))
 (SETQ pt4 (polar pt2 (dtr 120.0)(/ atstumas1 3)))
 (COMMAND "PLINE" pt3 "ARC" "Radius" (/ atstumas1 2) pt4 "Radius" (/ atstumas1 2) pt3 "")
 (SETQ Akis (entlast))
 (SETQ pt5 (polar pt1 (dtr 0.0)(/ Ilgis 2)))
 (SETQ pt6 (list (car pt5)(cadr pt3)))
 (SETQ Spindulys (/ atstumas1 9))
 (COMMAND "Circle" pt6 Spindulys)
 (SETQ Vyzdys (entlast))
 (COMMAND "HATCH" "ANSI38" 0.75 0 Trikampis Akis "")
 (COMMAND "HATCH" "SOLID" 2 0 Vyzdys "")
  )
