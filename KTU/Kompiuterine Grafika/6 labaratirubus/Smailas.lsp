(defun dtr (a)
    (* PI(/ a 180.0))); kampai laipsniais
; Smailas braižymas
(DEFUN c:smailas ()
 (SETQ Centras (GETPOINT "\n Nurodykite veidelio vietą"))
 (SETQ Spindulys (GETREAL "\n Įveskite veidelio spindulį"))
 (COMMAND "CIRCLE" Centras Spindulys) ; pagal centrą ir spindulį
 (SETQ Veidas (entlast))
 (COMMAND "osnap" "OFF")
;Burna
  (setq apt1 (polar Centras (dtr 0.0)(- Spindulys (* Spindulys 0.3))))
  (setq apt2 (polar Centras (dtr 180.0)(- Spindulys (* Spindulys 0.2))))
  (command "PLINE" apt1 apt2 "ARC" "Radius" (* Spindulys 0.75) apt1 "")
  (SETQ Burna (entlast))
  ;Akys
  (setq ppt1 (list(car apt1)(+(cadr apt1)(* Spindulys 0.1))))
  (setq ppt2 (list(-(car Centras)(* Spindulys 0.2))(+(cadr apt1)(* Spindulys 0.1))))
  (setq ppt3 (list(+(car Centras)(* Spindulys 0.1))(+(cadr apt1)(* Spindulys 0.1))))
  (setq ppt4 (list(car apt2)(+(cadr apt1)(* Spindulys 0.1))))
  (setq ppt5 (list(car ppt1)(+(cadr ppt1)(* Spindulys 0.1))))
  (setq ppt6 (list(car ppt3)(+(cadr ppt3)(* Spindulys 0.1))))
  (setq ppt7 (list(car ppt4)(+(cadr ppt4)(* Spindulys 0.1))))
  (setq ppt8 (list(car ppt2)(+(cadr ppt2)(* Spindulys 0.1))))
  (command "PLINE" ppt6 ppt3 ppt1 ppt5 "ARC" "Radius" (* Spindulys 0.3) ppt6  "")
  (SETQ Akis1 (entlast))
  (command "PLINE" ppt7 ppt4 ppt2 ppt8 "ARC" "Radius" (* Spindulys 0.3) ppt7 "")
  (SETQ Akis2 (entlast))
  (SETQ vpt1 (polar Centras (dtr 30.0)(* Spindulys 0.6)))
  (SETQ vpt2 (polar Centras (dtr 140.0)(* Spindulys 0.45)))
  (COMMAND "CIRCLE" vpt1 (* Spindulys 0.1))
  (SETQ Vyzdys1 (entlast))
  (COMMAND "CIRCLE" vpt2 (* Spindulys 0.1))
  (SETQ Vyzdys2 (entlast))
  (COMMAND "COLOR" "yellow")
  (COMMAND "HATCH" "SOLID" 2 0 Veidas Burna Akis1 Akis2 "" "")
  (COMMAND "COLOR" "magenta")
  (COMMAND "HATCH" "SOLID" 2 0 Burna "" "")
  (COMMAND "COLOR" "white")
  (COMMAND "HATCH" "SOLID" 2 0 Akis1 Akis2 Vyzdys1 Vyzdys2 "" "")
  (COMMAND "COLOR" "black")
  (COMMAND "HATCH" "SOLID" 2 0 Vyzdys1 Vyzdys2 "" ""))
