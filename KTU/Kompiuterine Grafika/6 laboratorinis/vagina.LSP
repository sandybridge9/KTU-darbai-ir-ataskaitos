(defun c:vagina ()
  (setq centras (getpoint "\n Áveskite centro koordinates"))
  (command "osnap" "off")
  (setq pt1 (list (car centras)(+(cadr centras)20)))
  (setq pt2 (list (car centras)(-(cadr centras)20)))
  (setq pt3 (list (-(car centras)20)(cadr centras)))
  (setq pt4 (list (+(car centras)20)(cadr centras)))
  (setq pt5 (list (-(car centras)5)(cadr centras)))
  (setq pt6 (list (+(car centras)5)(cadr centras)))
  (setq pt7 (list (+(car pt3)5)(cadr pt3)))
  (setq pt8 (list (-(car pt4)5)(cadr pt4)))
  (setq pt9 (list (car pt1)(+(cadr pt1)4)))
  (setq pt10 (list (car pt2)(-(cadr pt2)4)))
  (command "line" pt9 pt10 "")
  (command "pline" centras "width" 0 5 pt6 "width" 0 0 pt8 "width" 5 0 pt4 pt1 pt3 "width" 0 5 pt7 "width" 0 0 pt5 "width" 5 0 centras "")
  (command "line" pt3 pt2 pt4 ""))
