(defun c:falas ()
  (setq Pradinis (GETPOINT "\n Nurodykite viršutinį kairį figūros kampą"))
  (command "osnap" "off")
  (setq pt1 (list (+(car Pradinis)20)(cadr Pradinis)))
  (setq pt2 (list (car Pradinis)(-(cadr Pradinis)20)))
  (setq pt3 (list (+(car pt2)20)(cadr pt2)))
  (setq pt4 (list (+(car Pradinis)2)(cadr Pradinis)))
  (setq pt5 (list (-(car pt1)2)(cadr pt1)))
  (setq pt6 (list (+(car pt2)2)(cadr pt2)))
  (setq pt7 (list (-(car pt3)2)(cadr pt3)))
  (setq pt8 (list (car pt4)(+(cadr pt4)4)))
  (setq pt9 (list (car pt5)(+(cadr pt5)4)))
  (setq pt10 (list (car pt2)(-(cadr pt2)24)))
  (setq pt11 (list (-(car pt10)2)(-(cadr pt10)2)))
  (setq pt12 (list (-(car pt11)4)(cadr pt11)))
  (setq pt13 (list (car pt3)(-(cadr pt3)24)))
  (setq pt14 (list (+(car pt13)2)(-(cadr pt13)2)))
  (setq pt15 (list (+(car pt14)4)(cadr pt14)))
  (setq pt16 (list (+(car pt12)14)(-(cadr pt12)20)))
  (setq pt17 (list (car pt16)(+(cadr pt16)14)))
  (setq pt18 (list (+(car pt17)4)(cadr pt17)))
  (setq pt19 (list (car pt18)(-(cadr pt18)14)))
  (command "Pline" Pradinis pt10 "arc" pt11 "line" pt12 "arc" "radius" 15 pt16 "line" pt17 pt18 pt19 "arc" "radius" 15 pt15 "line" pt14 "arc" pt13 "line" pt1 pt9 pt8 Pradinis "")
  (command "Line" Pradinis pt1 "")
  (command "line" pt2 pt3 "")
  (command "line" pt4 pt6 "")
  (command "line" pt5 pt7 "")
  (command "line" pt11 pt14 ""))
