(defun c:pele ()
  (setq Pradinis (getpoint "\n Nurodykite viršutinio dešinio pelės kampo vietą"))
  (setq p1 (list (-(car Pradinis)10)(cadr Pradinis)))
  (setq p2 (list (-(car p1)20)(cadr p1)))
  (setq p3 (list (-(car p2)3)(-(cadr p2)3)))
  (setq p4 (list (car p3)(-(cadr p3)50)))
  (setq p5 (list (+(car p4)36)(cadr p4)))
  (setq p6 (list (car p5)(+(cadr p5)50)))
  (command "pline" Pradinis "width" 0 0 p2 "arc" p3 "line" p4 "arc" p5 "line" p6 "arc" Pradinis "")
  (setq p7 (list (car p6)(-(cadr p6)10)))
  (setq p8 (list (car p3)(-(cadr p3)10)))
  (setq p9 (list (-(car p7)13)(cadr p7)))
  (command "line" p7 p8 "")
  (command "line" p9 p1 "")
  (setq p10 (list (-(car p1)15)(+(cadr p1)15)))
  (setq p11 (list (-(car p10)15)(-(cadr p10)15)))
  (setq p12 (list (-(car p11)25)(-(cadr p11)25)))
  (setq p13 (list (-(car p12)15)(+(cadr p12)15)))
  (command "pline" p1 "width" 2 2 "arc" p10 p11 p12 p13 ""))
