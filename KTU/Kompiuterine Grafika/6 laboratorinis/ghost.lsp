; Vaiduoklio braižymas
(DEFUN c:ghost ()
 (SETQ Pagrindas (GETPOINT "\n Nurodykite vaiduoklio apatinį kairį kampą"))
 (SETQ Skersmuo (GETPOINT "\n Nurodykite vaiduoklio viršutinį dešinį kampą"))
 (COMMAND "osnap" "OFF")
 (SETQ apt1 (list(car Pagrindas) (cadr Skersmuo)))
 (SETQ apt2 (list(car Skersmuo) (cadr Pagrindas)))
 (COMMAND "PLINE" Pagrindas apt1 "ARC" Skersmuo "LINE" apt2 "")
 (SETQ atstumas1 (sqrt(+(EXPT(-(car apt2)(car Pagrindas))2)(EXPT(-(cadr apt2)(cadr Pagrindas))2))))
 (SETQ apt3 (list(+(car Pagrindas) (/ atstumas1 6)) (+(cadr Pagrindas) (/ atstumas1 6))))
 (SETQ apt4 (list(+(car Pagrindas) (/ atstumas1 3)) (-(cadr apt3) (/ atstumas1 6))))
 (SETQ apt5 (list(+(car Pagrindas) (/ atstumas1 2)) (+(cadr apt4) (/ atstumas1 6))))
 (SETQ apt6 (list(-(car apt2) (/ atstumas1 3)) (-(cadr apt5) (/ atstumas1 6))))
 (SETQ apt7 (list(-(car apt2) (/ atstumas1 6)) (+(cadr apt2) (/ atstumas1 6))))
 (COMMAND "LINE" Pagrindas apt3 apt4 apt5 apt6 apt7 apt2 "")
  ;akys
  (SETQ atstumas2 (sqrt(+(EXPT(-(car apt1)(car Pagrindas))2)(EXPT(-(cadr apt1)(cadr Pagrindas))2))))
  (SETQ apt8 (list(+(car apt1) (/ atstumas1 3)) (-(cadr apt1) (/ atstumas2 10))))
  (SETQ apt9 (list(-(car Skersmuo) (/ atstumas1 3)) (-(cadr Skersmuo) (/ atstumas2 10))))
  (COMMAND "CIRCLE" apt8 (/ atstumas1 6))
  (COMMAND "CIRCLE" apt9 (/ atstumas1 6)))
